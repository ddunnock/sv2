// Rule: SUBSETS must be followed by an OwnedSubsetting; the target is not optional.
// SysML 8.2.2.6.5 — Subsets = SUBSETS ownedRelationship += OwnedSubsetting
// SysML 8.2.2.1.2 — SUBSETS = ':>' | 'subsets'
part p :> ;
