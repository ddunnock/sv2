// Rule: TypedBy must be followed by a FeatureTyping; the type is not optional.
// SysML 8.2.2.6.5 — TypedBy = DEFINED_BY ownedRelationship += FeatureTyping
// SysML 8.2.2.1.2 — DEFINED_BY = ':' | 'defined' 'by'
part engine : ;
