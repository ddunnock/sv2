// Rule: a MemberPrefix carries at most one visibility.
// SysML 8.2.2.5.1 — MemberPrefix = ( visibility = VisibilityIndicator )?
// One optional slot, not a repetition.
public private package Vehicle;
