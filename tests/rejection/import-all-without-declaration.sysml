// Rule: 'all' qualifies an ImportDeclaration, it does not replace one.
// SysML 8.2.2.5.1 — Import = visibility 'import' ( isImportAll ?= 'all' )?
//                            ImportDeclaration RelationshipBody
public import all;
