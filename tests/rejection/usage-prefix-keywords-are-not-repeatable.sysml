// Rule: 'abstract' and 'variation' are alternatives to one another, so at most one
// may be written, and neither may be repeated.
// SysML 8.2.2.6.2 — RefPrefix = ( direction = FeatureDirection )?
//                               ( isDerived ?= 'derived' )?
//                               ( isAbstract ?= 'abstract' | isVariation ?= 'variation' )?
//                               ( isConstant ?= 'constant' )?
abstract variation part engine;
