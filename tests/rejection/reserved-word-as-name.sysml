// Rule: a reserved word cannot be a declaredName.
// KerML 8.2.2.6 — 'a reserved keyword is a token that has the lexical
// structure of a basic name but cannot actually be used as a basic name'.
// 'package' is on that list, so Identification has no declaredName here.
package package;
