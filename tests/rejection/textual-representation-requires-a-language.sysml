// Rule: a TextualRepresentation names its language; 'language' STRING_VALUE is required.
// SysML 8.2.2.4.3 — TextualRepresentation = ( 'rep' Identification )?
//   'language' language = STRING_VALUE body = REGULAR_COMMENT
public import A::* { rep inOCL /* self.x > 0 */ }
