// Rule: Crosses carries exactly one target and no repetition.
// SysML 8.2.2.6.5 — Crosses = CROSSES ownedRelationship += OwnedCrossSubsetting
// SysML 8.2.2.1.2 — CROSSES = '=>' | 'crosses'
part p => a, b;
