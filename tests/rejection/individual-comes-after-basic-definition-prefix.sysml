// Rule: 'individual' comes after the BasicDefinitionPrefix, never before it.
// SysML 8.2.2.9.1 — OccurrenceDefinitionPrefix = BasicDefinitionPrefix?
//   ( isIndividual ?= 'individual' ownedRelationship += EmptyMultiplicityMember )?
//   DefinitionExtensionKeyword*
individual abstract part def Vehicle;
