// REJECTED BY RULE. The semicolon is part of the production, not a statement
// separator the body supplies.
// SysML 8.2.2.5.1 — ElementFilterMember = MemberPrefix 'filter '
//                                         ownedRelatedElement += OwnedExpression ';'
package P { filter @Safety }
